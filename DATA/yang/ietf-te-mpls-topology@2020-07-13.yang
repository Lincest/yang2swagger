module ietf-te-mpls-topology {
     yang-version 1.1;
     namespace "urn:ietf:params:xml:ns:yang:ietf-te-mpls-topology";

     prefix "tet-mpls";

    import ietf-mpls-te-types {
        prefix "mte-types";
    }
     import ietf-network {
        prefix "nw";
     }

     import ietf-network-topology {
        prefix "nt";
     }

     import ietf-te-topology {
        prefix "tet";
     }

     import ietf-te-topology-packet {
        prefix "tet-pkt";
     }
    
      /*
      * import ietf-inet-types,created by xwu
      */
    import ietf-inet-types{
	    prefix "inet";
	}

     organization
       "Internet Engineering Task Force (IETF) TEAS WG";
     contact
       "WG Web:   <https://datatracker.ietf.org/wg/teas/>
        WG List:  <mailto:teas@ietf.org>

        Editor: Italo Busi
          <mailto:italo.busi@huawei.com>

        Editor: Haomian Zheng
          <mailto:zhenghaomian@huawei.com>

        Editor: Aihua Guo
          <mailto:aihuaguo.ietf@gmail.com>

        Editor: Xufeng Liu
          <mailto:xufeng.liu.ietf@gmail.com>";

     description
       "This module defines technology-specific MPLS-TE topology
        data model.

        Copyright (c) 2020 IETF Trust and the persons identified
        as authors of the code.  All rights reserved.

        Redistribution and use in source and binary forms, with
        or without modification, is permitted pursuant to, and
        subject to the license terms contained in, the Simplified
        BSD License set forth in Section 4.c of the IETF Trust's
        Legal Provisions Relating to IETF Documents
        (http://trustee.ietf.org/license-info).

        This version of this YANG module is part of RFC XXXX; see
        the RFC itself for full legal notices.";

    revision 2020-07-13 {
        description  "Initial Version";
        reference
            "draft-busizheng-teas-yang-te-mpls-topology";
    }
     /*
      * Groupings: add  mpls-bandwidth,  created by xwu;
      */
    grouping mpls-bandwidth{
        leaf mpls-bandwidth {
            type uint64{
                range "0..10000000000";
            }
            units "Kbps";
            description
                "Available bandwith value expressed in kilobits per second";
        }
    }
    grouping mpls-tp-attributes {
        description "tp attributes for mpls";
        leaf client-facing {
            type boolean;
            default 'false';
            description
                "Indicating if it is a client-facing TP.";
            }
                
        leaf tp-type{
            description 'termination-point type.' ;
            type enumeration {
                enum ETH {
                    value 1 ;
                    description 'ETH.' ;
                }
                enum ETH-TRUNK {
                    value 2 ;
                    description 'ETH-TRUNK.' ;
                }
            }
        }
    
        leaf ipv4-address{
            type inet:ipv4-prefix;
    	    description "ipv4 address and prefix";
        }
    
        leaf ipv6-address{
            type inet:ipv6-prefix;
    	    description "ipv6 address and prefix";
        }
    
        leaf mac{
            type string;
            description "MAC address";
        }
    
        leaf mtu{
            type uint32 {
                range 0..16777215;
            }
            description "mtu";
        }
    
        leaf speed {
            type uint64{
                range "0..10000000000";
            }
            units "bps";
            description "Available bandwith value expressed in bits per second";
        }
        leaf lag-mode{
            description 'lag mode.' ;
            type enumeration {
                enum Manual-LoadBalance {
                    value 0 ;
                    description 'Manual-LoadBalance.' ;
                }
                enum LACP-Static-LoadBalance {
                    value 1 ;
                    description 'LACP-Static-LoadBalance.' ;
                }
                enum LACP-Static-Non-LoadBalance {
                    value 2 ;
                    description 'LACP-Static-Non-LoadBalance.' ;
                }               
                enum Manual-Non-LoadBalance {
                    value 3 ;
                    description 'Manual-Non-LoadBalance.' ;
                }               
       
             }
        }
       
        leaf load-balance-mode{
            description 'termination-point type.' ;
            type enumeration {
                enum Non-LoadBalance {
                    value 0 ;
                    description 'Non-LoadBalance.' ;
                }
                enum SourceMac {
                    value 1 ;
                    description 'SourceMac' ;
                }
                enum DestinationMac {
                    value 2 ;
                    description 'DestinationMac.' ;
                }      
       
                enum SourceAndDestinationMac {
                    value 3 ;
                    description 'SourceAndDestinationMac.' ;
                }       
       
                enum SourceIP {
                    value 4 ;
                    description 'SourceIP.' ;
                }       
       
                enum DestinationIP {
                    value 5 ;
                    description 'DestinationIP.' ;
                }
                
                
                enum SourceAndDestinationIP {
                    value 6 ;
                    description 'SourceAndDestinationIP.' ;
                }               
                
                
                enum MPLSLabel {
                    value 7 ;
                    description 'MPLSLabel.' ;
                }               
                
                enum PacketAll {
                    value 8 ;
                    description 'PacketAll.' ;
                }
            }
        }
      
        leaf trunk-tp-id{
            type string;
            description "trunk-tp-id";
        }
    
    }//grouping end mpls-tp-attributes

    augment "/nw:networks/nw:network/nw:node/nt:termination-point/"
           + "tet:te/"
           + "tet:interface-switching-capability/tet:max-lsp-bandwidth/"
           + "tet:te-bandwidth/tet:technology" {
       when "../../../../../../nw:network-types/tet:te-topology/"
          + "tet-pkt:packet" {
        description
           "Augmentation parameters apply only for networks with
            Packet TE topology type.";
       }
        description "Augment maximum LSP TE bandwidth for the link termination point (LTP).";
        case packet {
            uses mte-types:te-packet-path-bandwidth;
        }
    }

    augment "/nw:networks/nw:network/nw:node/tet:te/"
           + "tet:te-node-attributes/tet:connectivity-matrices/"
           + "tet:path-constraints/tet:te-bandwidth/tet:technology" {
       when "../../../../../../nw:network-types/tet:te-topology/" + "tet-pkt:packet" {
        description
           "Augmentation parameters apply only for networks with
            Packet TE topology type.";
       }
       description
         "Augment TE bandwidth path constraints of the TE node
          connectivity matrices.";
       case packet {
            uses mte-types:te-packet-link-bandwidth;
       }
    }

    augment "/nw:networks/nw:network/nw:node/tet:te/"
           + "tet:te-node-attributes/tet:connectivity-matrices/"
           + "tet:connectivity-matrix/"
           + "tet:path-constraints/tet:te-bandwidth/tet:technology" {
        when "../../../../../../../nw:network-types/tet:te-topology/tet-pkt:packet" {
            description "Augmentation parameters apply only for networks with Packet TE topology type.";
        }
        description "Augment TE bandwidth path constraints of the connectivity matrix entry.";
        case packet {
            uses mte-types:te-packet-link-bandwidth;
        }
    }

    augment "/nw:networks/nw:network/nw:node/tet:te/"
           + "tet:information-source-entry/tet:connectivity-matrices/"
           + "tet:path-constraints/tet:te-bandwidth/tet:technology" {
        when "../../../../../../nw:network-types/tet:te-topology/tet-pkt:packet" {
            description
                "Augmentation parameters apply only for networks with Packet TE topology type.";
        }
        description
            "Augment TE bandwidth path constraints of the TE node connectivity matrices information source.";
        case packet {
            uses mte-types:te-packet-link-bandwidth;
        }
    }

    augment "/nw:networks/nw:network/nw:node/tet:te/"
           + "tet:information-source-entry/tet:connectivity-matrices/"
           + "tet:connectivity-matrix/"
           + "tet:path-constraints/tet:te-bandwidth/tet:technology" {
        when "../../../../../../../nw:network-types/tet:te-topology/tet-pkt:packet" {
            description
                "Augmentation parameters apply only for networks with
                Packet TE topology type.";
        }
        description
            "Augment TE bandwidth path constraints of the connectivity matrix entry information source";
        case packet {
            uses mte-types:te-packet-link-bandwidth;
        }
    }

    augment "/nw:networks/nw:network/nw:node/tet:te/"
           + "tet:tunnel-termination-point/"
           + "tet:client-layer-adaptation/tet:switching-capability/"
           + "tet:te-bandwidth/tet:technology" {
       when "../../../../../../nw:network-types/tet:te-topology/"
          + "tet-pkt:packet" {
         description
           "Augmentation parameters apply only for networks with
            Packet TE topology type.";
       }
       description
            "Augment client TE bandwidth of the tunnel termination point(TTP)";
       case packet {
            uses mte-types:te-packet-link-bandwidth;
       }
    }

    augment "/nw:networks/nw:network/nw:node/tet:te/"
           + "tet:tunnel-termination-point/"
           + "tet:local-link-connectivities/tet:path-constraints/"
           + "tet:te-bandwidth/tet:technology" {
        when "../../../../../../nw:network-types/tet:te-topology/tet-pkt:packet" {
            description
                "Augmentation parameters apply only for networks with Packet TE topology type.";
        }
        description
            "Augment TE bandwidth path constraints for the TTP Local Link Connectivities.";
        case packet {
            uses mte-types:te-packet-link-bandwidth;
        }
    }

    augment "/nw:networks/nw:network/nw:node/tet:te/"
           + "tet:tunnel-termination-point/"
           + "tet:local-link-connectivities/"
           + "tet:local-link-connectivity/tet:path-constraints/"
           + "tet:te-bandwidth/tet:technology" {
        when "../../../../../../../nw:network-types/tet:te-topology/tet-pkt:packet" {
            description "Augmentation parameters apply only for networks with Packet TE topology type.";
        }
        description
            "Augment TE bandwidth path constraints for the TTP Local Link Connectivity entry.";
        case packet {
            uses mte-types:te-packet-link-bandwidth;
        }
    }

    augment "/nw:networks/nw:network/nt:link/tet:te/"
           + "tet:te-link-attributes/"
           + "tet:interface-switching-capability/tet:max-lsp-bandwidth/"
           + "tet:te-bandwidth/tet:technology" {
        when "../../../../../../nw:network-types/tet:te-topology/tet-pkt:packet" {
            description "Augmentation parameters apply only for networks with Packet TE topology type.";
        }
        description
            "Augment maximum LSP TE bandwidth for the TE link.";
        case packet {
            uses mte-types:te-packet-path-bandwidth;
        }
    }

    augment "/nw:networks/nw:network/nt:link/tet:te/"
           + "tet:te-link-attributes/"
           + "tet:max-link-bandwidth/"
           + "tet:te-bandwidth/tet:technology" {
        when "../../../../../nw:network-types/tet:te-topology/tet-pkt:packet" {
            description
                "Augmentation parameters apply only for networks with
                    Packet TE topology type.";
        }
        description
            "Augment maximum TE bandwidth for the TE link";
        case packet {
            uses mte-types:te-packet-link-bandwidth;
        }
    }

    augment "/nw:networks/nw:network/nt:link/tet:te/"
           + "tet:te-link-attributes/"
           + "tet:max-resv-link-bandwidth/"
           + "tet:te-bandwidth/tet:technology" {
        when "../../../../../nw:network-types/tet:te-topology/tet-pkt:packet" {
            description
                "Augmentation parameters apply only for networks with
                    Packet TE topology type.";
        }
        description
            "Augment maximum reservable TE bandwidth for the TE link";
        case packet {
            uses mte-types:te-packet-link-bandwidth;
        }
    }

     augment "/nw:networks/nw:network/nt:link/tet:te/"
           + "tet:te-link-attributes/"
           + "tet:unreserved-bandwidth/"
           + "tet:te-bandwidth/tet:technology" {
        when "../../../../../nw:network-types/tet:te-topology/tet-pkt:packet" {
        description
            "Augmentation parameters apply only for networks with
                Packet TE topology type.";
        }
        description
            "Augment unreserved TE bandwidth for the TE Link";
        case packet {
            uses mte-types:te-packet-link-bandwidth;
        }
    }

     augment "/nw:networks/nw:network/nt:link/tet:te/"
           + "tet:information-source-entry/"
           + "tet:interface-switching-capability/"
           + "tet:max-lsp-bandwidth/"
           + "tet:te-bandwidth/tet:technology" {
        when "../../../../../../nw:network-types/tet:te-topology/tet-pkt:packet" {
        description
            "Augmentation parameters apply only for networks with
                Packet TE topology type.";
        }
        description
            "Augment maximum LSP TE bandwidth for the TE link information source";
        case packet {
            uses mte-types:te-packet-path-bandwidth;
        }
    }

     augment "/nw:networks/nw:network/nt:link/tet:te/"
           + "tet:information-source-entry/"
           + "tet:max-link-bandwidth/"
           + "tet:te-bandwidth/tet:technology" {
       when "../../../../../nw:network-types/tet:te-topology/"
          + "tet-pkt:packet" {
            description
                "Augmentation parameters apply only for networks with Packet TE topology type.";
       }
       description
            "Augment maximum TE bandwidth for the TE link information source";
       case packet {
            uses mte-types:te-packet-link-bandwidth;
       }
    }

    augment "/nw:networks/nw:network/nt:link/tet:te/"
           + "tet:information-source-entry/"
           + "tet:max-resv-link-bandwidth/"
           + "tet:te-bandwidth/tet:technology" {
        when "../../../../../nw:network-types/tet:te-topology/tet-pkt:packet" {
            description
                "Augmentation parameters apply only for networks with Packet TE topology type.";
        }
            description "Augment maximum reservable TE bandwidth for the TE link information-source";
            case packet {
                uses mte-types:te-packet-link-bandwidth;
            }
    }

    augment "/nw:networks/nw:network/nt:link/tet:te/"
           + "tet:information-source-entry/"
           + "tet:unreserved-bandwidth/"
           + "tet:te-bandwidth/tet:technology" {
        when "../../../../../nw:network-types/tet:te-topology/tet-pkt:packet" {
            description
                "Augmentation parameters apply only for networks with Packet TE topology type.";
        }
       description
            "Augment unreserved TE bandwidth of the TE link information source";
        case packet {
            uses mte-types:te-packet-link-bandwidth;
        }
    }

    augment "/nw:networks/tet:te/tet:templates/"
           + "tet:link-template/tet:te-link-attributes/"
           + "tet:interface-switching-capability/"
           + "tet:max-lsp-bandwidth/"
           + "tet:te-bandwidth/tet:technology" {
        description
            "Augment maximum LSP TE bandwidth of the TE link template";
        case packet {
            uses mte-types:te-packet-path-bandwidth;
        }
     }

     augment "/nw:networks/tet:te/tet:templates/"
           + "tet:link-template/tet:te-link-attributes/"
           + "tet:max-link-bandwidth/"
           + "tet:te-bandwidth/tet:technology" {
        description
            "Augment maximum TE bandwidth the TE link template";
        case packet {
            uses mte-types:te-packet-link-bandwidth;
        }
     }

     augment "/nw:networks/tet:te/tet:templates/"
           + "tet:link-template/tet:te-link-attributes/"
           + "tet:max-resv-link-bandwidth/"
           + "tet:te-bandwidth/tet:technology" {
        description
            "Augment maximum reservable TE bandwidth for the TE link template.";
        case packet {
            uses mte-types:te-packet-link-bandwidth;
        }
     }

     augment "/nw:networks/tet:te/tet:templates/"
           + "tet:link-template/tet:te-link-attributes/"
           + "tet:unreserved-bandwidth/"
           + "tet:te-bandwidth/tet:technology" {
        description
            "Augment unreserved TE bandwidth the TE link template";
        case packet {
            uses mte-types:te-packet-link-bandwidth;
        }
     }

     augment "/nw:networks/nw:network/nw:network-types/"
           + "tet:te-topology/tet-pkt:packet" {
        description
            "Augment network types to include MPLS-TE Topology Type";
        container mpls-topology {
            presence  "Indicates an MPLS-TE Topology Type.";
            description "Its presence indicates an MPLS-TE Topology";
        }
     }

    augment "/nw:networks/nw:network/nt:link/tet:te" {
        when "../../nw:network-types/tet:te-topology/tet-pkt:packet/tet-mpls:mpls-topology"  {
            description "Augment MPLS-TE Topology.";
        }
        description "Augment TE Link.";

        leaf load-balancing-type {
            type mte-types:load-balancing-type;
            default 'per-flow';
            description
           "Indicates the type of load-balancing (per-flow or per-LSP)
            performed by the bundled TE Link.
            This leaf is not present when the TE Link is not bundled.";
        }  // leaf load-balancing-type
     }

     augment "/nw:networks/nw:network/nw:node/nt:termination-point/tet:te" {
        when "../../../nw:network-types/tet:te-topology/tet-pkt:packet/tet-mpls:mpls-topology" {
            description "Augment MPLS-TE Topology.";
        }
        description "Augment LTP.";
        leaf uhp-incapable {
            type empty;
            config false;
            description
                "When present, indicates that the LTP is not capable to support Ultimate Hop Popping (UHP).";
        }   // leaf uhp-incapable
     }
     
     
     /*
      * Augmentations: new define MPLS-TE Topology Type, created by xwu;
      */

    augment "/nw:networks/nw:network/nw:network-types/tet:te-topology" {
        description
            "Augment network types to include MPLS-TE Topology Type, which not depend on packet";
        container mpls-topology {
            presence "Indicates an MPLS-TE Topology Type.";
            description "Its presence indicates an MPLS-TE Topology";
        }
     }
     
     
     

     
     /*
      * Augment: add NEW parameters in 'max-link-bandwidth' , created by xwu
      */
     augment "/nw:networks/nw:network/nt:link/tet:te/"
           + "tet:te-link-attributes/"
           + "tet:max-link-bandwidth/"
           + "tet:te-bandwidth/tet:technology" {
        when "../../../../../nw:network-types/tet:te-topology/tet-mpls:mpls-topology" {
            description
                "Augmentation parameters apply only for networks with MPLS topology type.";
        }
        description "Augment maximum TE bandwidth for the TE link";
        case mpls-topology {
           	uses mpls-bandwidth;
        }
     }
  
     /*
      * Augment: add NEW parameters in 'unreserved-bandwidth' , created by xwu
      */
     augment "/nw:networks/nw:network/nt:link/tet:te/"
           + "tet:te-link-attributes/"
           + "tet:unreserved-bandwidth/"
           + "tet:te-bandwidth/tet:technology" {
        when "../../../../../nw:network-types/tet:te-topology/tet-mpls:mpls-topology" {
            description
                "Augmentation parameters apply only for networks with MPLS topology type.";
        }
        description
            "Augment  unreserved bandwidth for the TE link";
        case mpls-topology {
           	uses mpls-bandwidth;
        }
     } 
  
      /*
      * Augment: add NEW parameters in 'te' , created by xwu
      */
    augment "/nw:networks/nw:network/nw:node/nt:termination-point/tet:te" {
        when "../../../nw:network-types/tet:te-topology/tet-mpls:mpls-topology" {
            description "Augmentation for TE termination point.";
        }
        description
            "Augmentation for TE termination point.";
        uses mpls-tp-attributes;
     }  

    rpc modify-tp-client-facing {
	     description "modify  attribute of termination point";		
	     	input { 
		     	leaf tp-id {
		        type nt:tp-id;
		        description
		          "Termination point identifier.";
		     				 }

		     	 leaf client-facing {
					      type boolean;
					      default 'false';
					      description
					        "Indicating if it is a client-facing TP.";
					 		   }
	       }//input end
	       
     }//RPC end
     
}
