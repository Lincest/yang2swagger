module ietf-mpls {
  yang-version 1.1;
  namespace "urn:ietf:params:xml:ns:yang:ietf-mpls";

  prefix "mpls";

  import ietf-routing {
    prefix "rt";
    reference "RFC8349: A YANG Data Model for Routing Management";
  }

  import ietf-routing-types {
    prefix "rt-types";
    reference "RFC6991: Common YANG Data Types";
  }

  import ietf-interfaces {
    prefix "if";
    reference "RFC7223: A YANG Data Model for Interface Management";
  }

  organization "IETF MPLS Working Group";

  contact
    "WG Web:   <http://tools.ietf.org/wg/mpls/>

     WG List:  <mailto:mpls@ietf.org>

     WG Chair: Loa Andersson
               <mailto:loa@pi.nu>

     WG Chair: Nic Leymann
               <mailto:N.Leymann@telekom.de>

     Editor:   Tarek Saad
               <mailto:tsaad@cisco.com>

     Editor:   Kamran Raza
               <mailto:skraza@cisco.com>

     Editor:   Rakesh Gandhi
               <mailto:rgandhi@cisco.com>

     Editor:   Xufeng Liu
               <mailto: xufeng.liu.ietf@gmail.com>

     Editor:   Vishnu Pavan Beeram
               <mailto:vbeeram@juniper.net>

     Editor:   Himanshu Shah
               <mailto:hshah@ciena.com>

     Editor:   Igor Bryskin
               <mailto: Igor.Bryskin@huawei.com>";

  description
    "This YANG module defines the essential components for the
     management of the MPLS subsystem.";

  revision "2018-10-10" {
    description
      "Latest revision:
        - Addressed MPLS-RT review comments";
    reference "RFC 3031: A YANG Data Model for base MPLS";
  }

  /* Identities */

    identity mpls {
        base rt:address-family;
        description
            "This identity represents the MPLS address family.";
    }

    identity label-block-alloc-mode {
        description
            "Base identity label-block allocation mode";
    }

    identity label-block-alloc-mode-manager {
        base label-block-alloc-mode;
        description
            "Label block allocation on reserved block is managed by label manager";
    }

    identity label-block-alloc-mode-application {
        base label-block-alloc-mode;
        description
            "Label block allocation on reserved block is managed by application";
    }

  /**
   * Typedefs
   */
  typedef mpls-operations-type {
    type enumeration {
      enum impose-and-forward {
        description
          "Operation impose outgoing label(s) and forward to
           next-hop";
      }
      enum pop-and-forward {
        description
          "Operation pop incoming label and forward to next-hop";
      }
      enum pop-impose-and-forward {
        description
          "Operation pop incoming label, impose one or more
           outgoing label(s) and forward to next-hop";
      }
      enum swap-and-forward {
        description
          "Operation swap incoming label, with outgoing label and
           forward to next-hop";
      }
      enum pop-and-lookup {
        description
          "Operation pop incoming label and perform a lookup";
      }
    }
    description "MPLS operations types";
  }

  typedef nhlfe-role {
    type enumeration {
      enum PRIMARY {
        description
          "Next-hop acts as primary traffic carrying";
      }
      enum BACKUP {
        description
          "Next-hop acts as backup";
      }
      enum PRIMARY_AND_BACKUP {
        description
          "Next-hop acts as primary and backup simultaneously";
      }
    }
    description "The next-hop role";
  }

  grouping nhlfe-single-contents {
    description
      "MPLS simple NHLFE contents";
    container remote-labels {
      description "Remote labels container";
      list remote-label {
        key "index";
        description "Remote label list";
        leaf index {
          type uint8 {
            range "0..255";
          }
          description
            "Index of the label. Index 0 indicates
             top of the label stack";
        }
        leaf label {
          type rt-types:mpls-label;
          description
            "The outgoing MPLS labels to impose";
        }
      }
    }
  }

  grouping nhlfe-multiple-contents {
    description
      "MPLS NHLFE contents";
    leaf index {
      type string;
      description
        "A user-specified identifier utilised to uniquely
         reference the next-hop entry in the next-hop list.
         The value of this index has no semantic meaning
         other than for referencing the entry.";
    }

    leaf backup-index {
      type string;
      description
        "A user-specified identifier utilised to uniquely
         reference the backup next-hop entry in the NHLFE list.
         The value of this index has no semantic meaning
         other than for referencing the entry.";
    }

    leaf loadshare {
      type uint16;
      description
        "This value is used to compute a loadshare to perform un-equal
         load balancing when multiple outgoing next-hop(s) are
         specified. A share is computed as a ratio of this number to the
         total under all next-hops(s).";
    }

    leaf role {
      type nhlfe-role;
      description "NHLFE role";
    }
    uses nhlfe-single-contents;
  }

  grouping interface-mpls-properties {
    description "MPLS interface contents grouping";
    leaf enabled {
      type boolean;
      description
        "'true' if mpls encapsulation is enabled on the
         interface. 'false' if mpls encapsulation is enabled
         on the interface.";
    }
    leaf mtu {
      type uint32;
      description
        "MPLS Maximum Transmission Unit (MTU) in bytes";
    }
  }

  grouping interfaces-mpls {
    description "List of MPLS interfaces";
    list interface {
      key "name";
      description "List of MPLS interfaces";
      leaf name {
        type if:interface-ref;
        description
          "The name of a configured MPLS interface";
      }
      uses interface-mpls-properties;
    }
  }

  grouping label-block-properties {
    description "Label-block configuration items";
    leaf index {
      type string;
      description
        "A user-specified identifier utilised to uniquely
         reference an MPLS label block";
    }
    leaf start-label {
      type rt-types:mpls-label;
      description "Label-block start";
    }
    leaf end-label {
      type rt-types:mpls-label;
      description "Label-block end";
    }
    leaf block-allocation-mode {
      type identityref {
        base label-block-alloc-mode;
      }
      description "Label-block allocation mode";
    }
  }

  grouping globals {
    description "MPLS global configuration grouping";
    leaf ttl-propagate {
      type boolean;
      default 'true';
      description "Propagate TTL between IP and MPLS";
    }
  }
    grouping label-blocks {
        description "Label-block allocation grouping";
        container label-blocks {
            description "Label-block allocation container";
            list label-block {
                must "start-label >= end-label" {
                    error-message "start-label can not be less than end-label";
                }
                key index;
                unique "start-label end-label";
                description "List of MPLS label-blocks";
                uses label-block-properties;
                container state {
                    config false;
                    description "Holds state information";
                    //uses label-block_state;
                    leaf free-labels-count {
                        when "../../block-allocation-mode = 'mpls:label-block-alloc-mode-manager'";
                        type uint32;
                        description "Label-block free labels count";
                    }
                    leaf inuse-labels-count {
                        when "../../block-allocation-mode = 'mpls:label-block-alloc-mode-manager'";
                        type uint32;
                        description "Label-block inuse labels count";
                    }
                }
            }
        }
    }

    augment "/rt:routing" {
        description "MPLS augmentation.";
        container mpls {
            description
                "MPLS container, to be used as an augmentation target node other MPLS sub-features config, e.g. MPLS static LSP, MPLS
                LDP LSPs, and Trafic Engineering MPLS LSP Tunnels, etc.";
            uses globals;
            uses label-blocks;
            uses interfaces-mpls;
        }
    }

  /* MPLS routes augmentation */
    augment "/rt:routing/rt:ribs/rt:rib/rt:routes/rt:route" {
        when "derived-from-or-self(../../rt:address-family,'mpls:mpls')" {
        description
            "This augment is valid only for IPv4 unicast.";
        }
        description
            "This leaf augments an MPLS routes.";
        leaf local-label {
            type rt-types:mpls-label;
            description
                "MPLS local label.";
        }
    }

  /* MPLS simple-next-hop augmentation */
  augment "/rt:routing/rt:ribs/rt:rib/rt:routes/rt:route/"
        + "rt:next-hop/rt:next-hop-options/rt:simple-next-hop" {
    when "derived-from-or-self(../../../rt:address-family, "
       + "'mpls:mpls')" {
      description
        "This augment is valid only for IPv4 unicast.";
    }
    description
      "Augment 'simple-next-hop' case in IPv4 unicast routes.";
    uses nhlfe-single-contents;
  }

  /* MPLS next-hop-list augmentation */
  augment "/rt:routing/rt:ribs/rt:rib/rt:routes/rt:route/"
        + "rt:next-hop/rt:next-hop-options/rt:next-hop-list/"
        + "rt:next-hop-list/rt:next-hop" {
    when "derived-from-or-self(../../../../../rt:address-family, "
       + "'mpls:mpls')" {
      description
        "This augment is valid only for IPv4 unicast.";
    }
    description
      "This leaf augments the 'next-hop-list' case of IPv4 unicast
       routes.";
    uses nhlfe-multiple-contents;
  }

  /* MPLS RPC input augmentation */

/*
    augment "/rt:routing/rt:ribs/rt:rib/rt:active-route/rt:input" {//input是利用augment直接加到routing.yang中active-route这个action中的，而不需要原位置上就一定要有input；感觉input比较特殊，支持原位置上没有而加上input；
        description "This augment adds the input parameter of the 'active-route'action.";
        leaf local-label {
            type rt-types:mpls-label;
            description "MPLS local label.";
        }
    }//0825晚上和吴翔讨论这个位置vscode和designer报错不一致。结论是将此位置进行注释掉。
 */


  /* MPLS RPC output augmentation */
  augment "/rt:routing/rt:ribs/rt:rib/rt:active-route/"
        + "rt:output/rt:route/"
        + "rt:next-hop/rt:next-hop-options/rt:simple-next-hop" {
    description
      "This augment adds the destination prefix to the reply of the
       'active-route' action.";
    uses nhlfe-multiple-contents;
  }
  augment "/rt:routing/rt:ribs/rt:rib/rt:active-route/"
        + "rt:output/rt:route/"
        + "rt:next-hop/rt:next-hop-options/rt:next-hop-list/"
        + "rt:next-hop-list/rt:next-hop" {
    description
      "This augment adds the destination prefix to the reply of the
       'active-route' action.";
    uses nhlfe-multiple-contents;
  }
}
