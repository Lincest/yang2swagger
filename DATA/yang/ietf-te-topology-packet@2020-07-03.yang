module ietf-te-topology-packet {
     yang-version 1.1;
     namespace "urn:ietf:params:xml:ns:yang:ietf-te-topology-packet";

     prefix "tet-pkt";

     import ietf-network {
       prefix "nw";
       reference
         "RFC 8345: A YANG Data Model for Network Topologies";
     }

     import ietf-network-topology {
       prefix "nt";
       reference
         "RFC 8345: A YANG Data Model for Network Topologies";
     }

     import ietf-routing-types {
       prefix "rt-types";
       reference
         "RFC 8294: Common YANG Data Types for the Routing Area";
     }

     import ietf-te-topology {
       prefix "tet";
       reference
         "I-D.ietf-teas-yang-te-topo: YANG Data Model for Traffic
          Engineering (TE) Topologies";
     }

     import ietf-te-types {
       prefix "te-types";
       reference
         "I-D.ietf-teas-yang-te-types: Traffic Engineering Common YANG
          Types";
     }

     import ietf-te-packet-types {
       prefix "te-packet-types";
       reference
         "I-D.ietf-teas-yang-te-types: Traffic Engineering Common YANG
          Types";
     }

     organization
       "Traffic Engineering Architecture and Signaling (TEAS)
        Working Group";

     contact
       "WG Web:   <http://tools.ietf.org/wg/teas/>
        WG List:  <mailto:teas@ietf.org>

        Editor:   Xufeng Liu
                  <mailto:xufeng.liu.ietf@gmail.com>

        Editor:   Igor Bryskin
                  <mailto:Igor.Bryskin@huawei.com>

        Editor:   Vishnu Pavan Beeram
                  <mailto:vbeeram@juniper.net>

        Editor:   Tarek Saad
                  <mailto:tsaad@cisco.com>

        Editor:   Himanshu Shah
                  <mailto:hshah@ciena.com>

        Editor:   Oscar Gonzalez De Dios
                  <mailto:oscar.gonzalezdedios@telefonica.com>";

     description
       "YANG data model for representing and manipulating PSC (Packet
        Switching) TE Topologies.

        Copyright (c) 2018 IETF Trust and the persons identified as
        authors of the code.  All rights reserved.

        Redistribution and use in source and binary forms, with or
        without modification, is permitted pursuant to, and subject to
        the license terms contained in, the Simplified BSD License set
        forth in Section 4.c of the IETF Trust's Legal Provisions
        Relating to IETF Documents
        (http://trustee.ietf.org/license-info).

        This version of this YANG module is part of RFC XXXX; see the
        RFC itself for full legal notices.";

     revision 2020-07-03 {

       description
         "Initial revision";
       reference
         "RFC XXXX: YANG Data Model for Layer 3 TE Topologies";
     }

     /*
      * Features
      */

     feature te-performance-metric {
       description
         "This feature indicates that the system supports
          TE performance metric.";
       reference
         "RFC7471: OSPF Traffic Engineering (TE) Metric Extensions.
          RFC8570: IS-IS Traffic Engineering (TE) Metric Extensions.
          RFC7823: Performance-Based Path Selection for Explicitly
          Routed Label Switched Paths (LSPs) Using TE Metric
          Extensions";
     }

     /*
      * Groupings
      */
     grouping packet-switch-capable-container {
       description
         "The container of packet switch capable attributes.";
       container packet-switch-capable {
         description
           "Interface has packet-switching capabilities.";
         leaf minimum-lsp-bandwidth {
           type rt-types:bandwidth-ieee-float32;
           description
             "Minimum LSP Bandwidth. Units in bytes per second";
         }
         leaf interface-mtu {
           type uint16;
           description
             "Interface MTU.";
         }
       }
     }

     /*
      * Augmentations
      */
     /* Augmentations to network-types */

     augment "/nw:networks/nw:network/nw:network-types/"
       + "tet:te-topology" {
       description
         "Defines the packet TE topology type.";
       container packet {
         presence "Indicates packet TE topology.";
         description
           "Its presence identifies the packet TE topology type.";
       }
     }

     /* Augmentations to connectivity-matrix */
     augment "/nw:networks/nw:network/nw:node/tet:te/"
       + "tet:te-node-attributes/tet:connectivity-matrices" {
       when "../../../../nw:network-types/tet:te-topology/"
         + "tet-pkt:packet" {
         description
           "Augment only for packet TE topology";
       }
       description
         "Parameters for PSC TE topology.";
       uses te-packet-types:performance-metrics-attributes-packet {
         if-feature te-performance-metric;
         refine performance-metrics-one-way {
           config false;
         }
         refine performance-metrics-two-way {
           config false;
         }
       }
       uses
         te-packet-types:performance-metrics-throttle-container-packet {
         if-feature te-performance-metric;
       }
     }

     augment "/nw:networks/nw:network/nw:node/tet:te/"
           + "tet:te-node-attributes/tet:connectivity-matrices/"
           + "tet:connectivity-matrix" {
       when "../../../../../nw:network-types/tet:te-topology/"
         + "tet-pkt:packet" {
         description
           "Augment only for packet TE topology";
       }
       description
         "Parameters for PSC TE topology.";
       uses te-packet-types:performance-metrics-attributes-packet {
         if-feature te-performance-metric;
         refine performance-metrics-one-way {
           config false;
         }
         refine performance-metrics-two-way {
           config false;
         }
       }
       uses
         te-packet-types:performance-metrics-throttle-container-packet {
         if-feature te-performance-metric;
       }
     }

     augment "/nw:networks/nw:network/nw:node/tet:te/"
           + "tet:information-source-entry/tet:connectivity-matrices" {
       when "../../../../nw:network-types/tet:te-topology/"
         + "tet-pkt:packet" {
         description
           "Augment only for packet TE topology";
       }
       description
         "Parameters for PSC TE topology.";
       uses te-packet-types:performance-metrics-attributes-packet {
         if-feature te-performance-metric;
       }
       uses
         te-packet-types:performance-metrics-throttle-container-packet {
         if-feature te-performance-metric;
       }
     }

     augment "/nw:networks/nw:network/nw:node/tet:te/"
           + "tet:information-source-entry/tet:connectivity-matrices/"
           + "tet:connectivity-matrix" {
       when "../../../../../nw:network-types/tet:te-topology/"
         + "tet-pkt:packet" {
         description
           "Augment only for packet TE topology";
       }
       description
         "Parameters for PSC TE topology.";
       uses te-packet-types:performance-metrics-attributes-packet {
         if-feature te-performance-metric;
       }
       uses
         te-packet-types:performance-metrics-throttle-container-packet {
         if-feature te-performance-metric;
       }

     }

     /* Augmentations to tunnel-termination-point */
     augment "/nw:networks/nw:network/nw:node/tet:te/"
           + "tet:tunnel-termination-point/"
           + "tet:local-link-connectivities" {
       when "../../../../nw:network-types/tet:te-topology/"
         + "tet-pkt:packet" {
         description
           "Augment only for packet TE topology";
       }
       description
         "Parameters for PSC TE topology.";
       uses te-packet-types:performance-metrics-attributes-packet {
         if-feature te-performance-metric;
         refine performance-metrics-one-way {
           config false;
         }
         refine performance-metrics-two-way {
           config false;
         }
       }
       uses
         te-packet-types:performance-metrics-throttle-container-packet {
         if-feature te-performance-metric;
       }
     }

     augment "/nw:networks/nw:network/nw:node/tet:te/"
           + "tet:tunnel-termination-point/"
           + "tet:local-link-connectivities/"
           + "tet:local-link-connectivity" {
       when "../../../../../nw:network-types/tet:te-topology/"
         + "tet-pkt:packet" {
         description
           "Augment only for packet TE topology";
       }
       description
         "Parameters for PSC TE topology.";
       uses te-packet-types:performance-metrics-attributes-packet {
         if-feature te-performance-metric;
         refine performance-metrics-one-way {
           config false;
         }
         refine performance-metrics-two-way {
           config false;
         }
       }


       uses
         te-packet-types:performance-metrics-throttle-container-packet {
         if-feature te-performance-metric;
       }
     }

     /* Augmentations to te-link-attributes */
     augment "/nw:networks/tet:te/tet:templates/"
           + "tet:link-template/tet:te-link-attributes" {
       when "tet:interface-switching-capability "
         + "[tet:switching-capability = 'te-types:switching-psc1']" {
         description
           "Valid only for PSC";
       }
       description
         "Parameters for PSC TE topology.";
       uses te-packet-types:performance-metrics-attributes-packet {
         if-feature te-performance-metric;
         refine performance-metrics-one-way {
           config false;
         }
         refine performance-metrics-two-way {
           config false;
         }
       }
       uses
         te-packet-types:performance-metrics-throttle-container-packet {
         if-feature te-performance-metric;
       }
     }

     augment "/nw:networks/nw:network/nt:link/tet:te/"
           + "tet:te-link-attributes" {
       when "(../../../nw:network-types/tet:te-topology/tet-pkt:packet)"
         + " and (tet:interface-switching-capability "
         + "[tet:switching-capability = 'te-types:switching-psc1'])" {
         description
           "Valid only for PSC";
       }
       description
         "Parameters for PSC TE topology.";
       uses te-packet-types:performance-metrics-attributes-packet {
         if-feature te-performance-metric;
         refine performance-metrics-one-way {
           config false;
         }
         refine performance-metrics-two-way {
           config false;

         }
       }
       uses
         te-packet-types:performance-metrics-throttle-container-packet {
         if-feature te-performance-metric;
       }
     }

     augment "/nw:networks/nw:network/nt:link/tet:te/"
           + "tet:information-source-entry" {
       when "(../../../nw:network-types/tet:te-topology/tet-pkt:packet)"
         + " and (tet:interface-switching-capability "
         + "[tet:switching-capability = 'te-types:switching-psc1'])" {
         description
           "Valid only for PSC";
       }
       description
         "Parameters for PSC TE topology.";
       uses te-packet-types:performance-metrics-attributes-packet {
         if-feature te-performance-metric;
       }
       uses
         te-packet-types:performance-metrics-throttle-container-packet {
         if-feature te-performance-metric;
       }
     }

     /* Augmentations to interface-switching-capability */
     augment "/nw:networks/tet:te/tet:templates/"
           + "tet:link-template/tet:te-link-attributes/"
           + "tet:interface-switching-capability" {
       when "tet:switching-capability = 'te-types:switching-psc1' " {
         description
           "Valid only for PSC";
       }
       description
         "Parameters for PSC TE topology.";
       uses packet-switch-capable-container;
     }

     augment "/nw:networks/nw:network/nt:link/tet:te/"
           + "tet:te-link-attributes/"
           + "tet:interface-switching-capability" {
       when "(../../../../nw:network-types/tet:te-topology/"
         + "tet-pkt:packet) and "
         + "(tet:switching-capability = 'te-types:switching-psc1')" {
         description
           "Valid only for PSC";
       }
       description
         "Parameters for PSC TE topology.";
       uses packet-switch-capable-container;
     }

     augment "/nw:networks/nw:network/nt:link/tet:te/"
           + "tet:information-source-entry/"
           + "tet:interface-switching-capability" {
       when "(../../../../nw:network-types/tet:te-topology/"
         + "tet-pkt:packet) and "
         + "(tet:switching-capability = 'te-types:switching-psc1')" {
         description
           "Valid only for PSC";
       }
       description
         "Parameters for PSC TE topology.";
       uses packet-switch-capable-container;
     }
   }
