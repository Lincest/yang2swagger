module ietf-l2vpn-ntw {
    yang-version 1.1;
    namespace "urn:ietf:params:xml:ns:yang:ietf-l2vpn-ntw";
    prefix l2vpn-ntw;

    import ietf-inet-types {
        prefix inet;
        reference
            "Section 4 of RFC 6991";
    }
    import ietf-yang-types {
        prefix yang;
        reference
            "Section 3 of RFC 6991";
    }
    import ietf-vpn-common {
        prefix vpn-common;
        reference
            "RFC CCCC: A Layer 2/3 VPN Common YANG Model";
    }
    
  
  /* Import routing types -- create by xwu*/
    import ietf-routing-types {
        prefix "rt-types";
        reference "RFC6991: Common YANG Data Types";
    }
  
    /* Import ietf te mpls -- create by xwu*/
    import ietf-te-mpls {
        prefix "te-mpls";
        reference "A YANG Data Model for MPLS Traffic Engineering Tunnels and Interfaces.";
    }
  

  organization
    "IETF OPSA (Operations and Management Area) Working Group";
  contact
    "WG Web:   <http://tools.ietf.org/wg/opsawg/>
     WG List:  <mailto:opsawg@ietf.org>

     Editor:    Samier Barguil
               <mailto:samier.barguilgiraldo.ext@telefonica.com>
     Editor:    Oscar Gonzalez de Dios
               <mailto:oscar.gonzalezdedios@telefonica.com>
     Editor:    Mohamed Boucadair
               <mailto:mohamed.boucadair@orange.com>";
  description
    "This YANG module defines a generic network model
     for Layer 2 VPN services.

     Copyright (c) 2021 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

    revision 2021-07-30 {
        description
            "Initial version.";
        reference
            "RFC XXXX: A Layer 2 VPN Network YANG Model.";
    }

  /* Features */

    feature multicast-like {
        description
            "Indicates the support of multicast-like capabilities in a L2VPN.";
    }
    feature target-sites {
        description
            "Indicates the support of 'target-sites' match flow parameter.";
    }

    feature l2cp-control {
        description
            "Indicates the support of L2CP control.";
    }

    feature output-bw {
        description
            "Indicates the support of Output Bandwidth in a VPN";
    }

    feature uni-list {
        description
            "Indicates thesupport of UNI list in a VPN.";
    }

    feature oam-3ah {
        description
            "Indicates the support of OAM 802.3ah.";
    }

    feature micro-bfd {
        description
            "Indicates the support of Micro-BFD.";
    }

    feature signaling-options {
        description
            "Indicates the support of signalling option.";
    }

    feature always-on {
        description
            "Indicates the support for always-on access constraint.";
    }

    feature requested-type {
        description
            "Indicates the support for requested-type access constraint.";
    }
  feature vlan {
    description
      "Indicates the support of VLAN.";
  }

  feature sub-inf {
    description
      "Indicates the support of Sub Interface.";
  }

  feature atm {
    description
      "Indicates the support of ATM.";
  }

  feature vxlan {
    description
      "Indicates the support of VxLAN.";
  }

  feature lan-tag {
    description
      "Indicates the LAN Tag support in a VPN.";
  }

  /* Typedefs */
  /* Identities */

  identity evpn-redundancy-mode {
    description
      "Base identity for EVPN redundancy modes.";
  }

  identity single-active {
    base evpn-redundancy-mode;
    description
      "Indicates Single-Active redundancy mode for
       a given Ethernet Segment (ES).";
    reference
      "RFC 7432: BGP MPLS-Based Ethernet VPN, Section 14.1.1";
  }

  identity all-active {
    base evpn-redundancy-mode;
    description
      "Indicates All-Active redundancy mode for
       a given Ethernet Segment (ES).";
    reference
      "RFC 7432: BGP MPLS-Based Ethernet VPN, Section 14.1.2";
  }

  identity evpn-service-type {
    description
      "Base identity for EVPN service type.";
  }

  identity vlan-based-service-interface {
    base evpn-redundancy-mode;
    description
      "VLAN-Based Service Interface.";
    reference
      "RFC 7432: BGP MPLS-Based Ethernet VPN, Section 6.1";
  }

  identity vlan-bundle-service-interface {
    base evpn-redundancy-mode;
    description
      "VLAN Bundle Service Interface.";
    reference
      "RFC 7432: BGP MPLS-Based Ethernet VPN, Section 6.2";
  }

  identity vlan-aware-bundle-service-interface {
    base evpn-redundancy-mode;
    description
      "VLAN-Aware Bundle Service Interface.";
    reference
      "RFC 7432: BGP MPLS-Based Ethernet VPN, Section 6.3";
  }

  identity mapping-type {
    base vpn-common:multicast-gp-address-mapping;
    description
      "Identity for mapping type.";
  }

  identity protection-mode {
    description
      "Identity of protection mode";
  }

  identity oneplusone {
    base protection-mode;
    description
      "In this scheme, the primary circuit will be
       protected by a backup circuit, typically meeting certain
       diverse path/fiber/site/node criteria.  Both primary and
       protection circuits are provisioned to be in the active
       forward ing state. The subscriber may choose to send the
       same service frames across both circuits simultaneously.";
  }

  identity one-to-one {
    base protection-mode;
    description
      "In this scheme, a backup circuit to the primary
       circuit is provisioned.  Depending on the implementation
       agreement, the protection circuits may either always be
       in active forwarding state, or may only become active when
       a faulty state is detected on the primary circuit.";
  }

  identity bundling-type {
    description
      "The base identity for the bundling type.  It supports
       multiple CE-VLANs associated with an L2VPN service or
       all CE-VLANs associated with an L2VPN service.";
  }

  identity multi-svc-bundling {
    base bundling-type;
    description
      "Identity for multi-service bundling, i.e.,
       multiple CE-VLAN IDs can be associated with an
       L2VPN service at a site.";
  }

  identity one2one-bundling {
    base bundling-type;
    description
      "Identity for one-to-one service bundling, i.e.,
       each L2VPN can be associated with only one CE-VLAN ID
       at a site.";
  }

  identity all2one-bundling {
    base bundling-type;
    description
      "Identity for all-to-one bundling, i.e., all CE-VLAN IDs
       are mapped to one L2VPN service.";
  }

  identity color-id {
    description
      "Base identity of the color ID.";
  }

  identity color-id-cvlan {
    base color-id;
    description
      "Identity of the color ID based on a CVLAN.";
  }

  identity color-type {
    description
      "Identity of color types.";
  }

  identity green {
    base color-type;
    description
      "Identity of the 'green' color type.";
  }

  identity yellow {
    base color-type;
    description
      "Identity of the 'yellow' color type.";
  }

  identity red {
    base color-type;
    description
      "Identity of the 'red' color type.";
  }

  identity perf-tier-opt {
    description
      "Identity of performance tier option.";
  }

  identity metro {
    base perf-tier-opt;
    description
      "Identity of metro";
  }

  identity regional {
    base perf-tier-opt;
    description
      "Identity of regional";
  }
  identity continental {
    base perf-tier-opt;
    description
      "Identity of continental";
  }

  identity global {
    base perf-tier-opt;
    description
      "Identity of global";
  }

  identity policing {
    description
      "Identity of policing type";
  }

  identity one-rate-two-color {
    base policing;
    description
      "Identity of one-rate, two-color (1R2C)";
  }

  identity two-rate-three-color {
    base policing;
    description
      "Identity of two-rate, three-color (2R3C)";
  }

  identity loop-prevention-type {
    description
      "Identity of loop prevention.";
  }

  identity shut {
    base loop-prevention-type;
    description
      "Identity of shut protection.";
  }

  identity trap {
    base loop-prevention-type;
    description
      "Identity of trap protection.";
  }

  identity t-ldp-pwe-type {
    description
      "Identity for t-ldp-pwe-type.";
  }

  identity vpws-type {
    base t-ldp-pwe-type;
    description
      "Identity for VPWS";
  }

  identity vpls-type {
    base t-ldp-pwe-type;
    description
      "Identity for vpls";
  }

  identity hvpls {
    base t-ldp-pwe-type;
    description
      "Identity for h-vpls";
  }

  identity l2vpn-type {
    description
      "Layer 2 VPN types";
  }

  identity l2vpn-vpws {
    base l2vpn-type;
    description
      "VPWS L2VPN type.";
  }

  identity l2vpn-vpls {
    base l2vpn-type;
    description
      "VPLS L2VPN type.";
  }

  identity distribute-vpls {
    base l2vpn-type;
    description
      "distribute VPLS L2VPN type.";
  }

  identity evpn-type {
    description
      "Ethernet VPN types";
  }
  identity evpn-vpws {
    base evpn-type;
    description
      "VPWS support in EVPN.";
  }

  identity evpn-pbb {
    base evpn-type;
    description
      " Provider Backbone Bridging Support in EVPN.";
  }

  identity pm-type {
    description
      "Performance-monitoring type.";
  }

  identity loss {
    base pm-type;
    description
      "Loss measurement.";
  }

  identity delay {
    base pm-type;
    description
      "Delay measurement.";
  }

  identity mac-learning-mode {
    description
      "MAC learning mode.";
  }

  identity data-plane {
    base mac-learning-mode;
    description
      "User MAC addresses are learned through ARP broadcast.";
  }

  identity control-plane {
    base mac-learning-mode;
    description
      "User MAC addresses are advertised through EVPN-BGP.";
  }

  identity mac-action {
    description
      "Base identity for a MAC action.";
  }

  identity drop {
    base mac-action;
    description
      "Identity for dropping a packet.";
  }

  identity flood {
    base mac-action;
    description
      "Identity for packet flooding.";
  }

  identity warning {
    base mac-action;
    description
      "Identity for sending a warning log message.";
  }

  identity load-balance-method {
    description
      "Base identity for load balance method.";
  }

  identity fat-pw {
    base load-balance-method;
    description
      "Identity for Fat PW. Fat label is
       applied to Pseudowires across MPLS
       network.";
  }

  identity entropy-label {
    base load-balance-method;
    description
      "Identity for entropy label.Entropy label
       is applied to IP forwarding,
       L2VPN or L3VPN across MPLS network";
  }

  identity vxlan-source-port {
    base load-balance-method;
    description
      "Identity for vxlan source port.VxLAN
       Source Port is one load balancing method.";
  }
  identity precedence-type {
    description
      "Redundancy type. The service can be created
       with active and bakcup signalization.";
  }

  identity primary {
    base precedence-type;
    description
      "Identifies the Main L2VPN.";
  }

  identity backup {
    base precedence-type;
    description
      "Identifies the Backup L2VPN.";
  }

  /* Groupings */

  grouping cfm-802-grouping {
    description
      "Grouping for 802.1ag CFM attribute";
    leaf maid {
      type string;
      description
        "MA ID";
    }
    leaf mep-id {
      type uint32;
      description
        "Local MEP ID";
    }
    leaf mep-level {
      type uint32;
      description
        "MEP level";
    }
    leaf mep-up-down {
      type enumeration {
        enum up {
          description
            "MEP up";
        }
        enum down {
          description
            "MEP down";
        }
      }
      description
        "MEP up/down";
    }
    leaf remote-mep-id {
      type uint32;
      description
        "Remote MEP ID";
    }
    leaf cos-for-cfm-pdus {
      type uint32;
      description
        "COS for CFM PDUs";
    }
    leaf ccm-interval {
      type uint32;
      description
        "CCM interval";
    }
    leaf ccm-holdtime {
      type uint32;
      description
        "CCM hold time";
    }
    
    
  //  'ccm-priority-type' haven't define in 'ietf-vpn-common.yang', so Comment on these lines, modify by xwu
  //  leaf ccm-p-bits-pri {
  //    type vpn-common:ccm-priority-type;
  //    description
  //      "The priority parameter for CCMs transmitted by the MEP";
 //   }
    
    
  }


  /* Main L2NM Container */
    container l2vpn-ntw {
        description
            "Container for L2NM.";
        container vpn-profiles {
            description
                "Container for VPN profiles.";
            uses vpn-common:vpn-profile-cfg;
        }
        container vpn-services {
            description
                "Container for L2VPN service";
            list vpn-service {
                key "vpn-id";
                description
                    "Container of port configurations";
                uses vpn-common:vpn-description;
                leaf parent-service-id {
                    type vpn-common:vpn-id;
                    description
                        "Pointer to the parent service that triggered the L2NM.";
                }
                leaf vpn-svc-type {
                    type identityref {
                        base vpn-common:service-type;
                    }
                    description
                        "Service type";
                }
                container global-parameters-profiles {
                    description
                        "Container for a list of VPN instance profiles.";
                    list global-parameters-profile {
                        key "profile-id";
                        description
                            "List of XXX.";
                        leaf profile-id {
                            type string;
                            description
                                "profile identifier.";
                        }
                    }
                }
        
                uses vpn-common:service-status;
                container vpn-nodes {
                    description
                        "Set fo VPN nodes that are involved in the L2NM.";
                    list vpn-node {
                        key "vpn-node-id";
                        description
                            "Container of VPN Nodes.";
                        leaf vpn-node-id {
                            type vpn-common:vpn-id;
                            description
                                "VPN Node indentifier";
                        }
                    leaf description {
                        type string;
                        description
                            "Textual description of a VPN node.";
                    }
                    leaf ne-id {
                        type string;
                        description
                            "NE IP address";
                    }
                    leaf role {
                        type identityref {
                            base vpn-common:role;
                        }
                        default "vpn-common:any-to-any-role";
                        description
                            "Role of the VPN node in the VPN.";
                    }
                    container active-global-parameters-profiles {
                        description
                            "Container for a list of VPN instance profiles.";
                        list global-parameters-profile {
                            key "profile-id";
                            description
                                "List of XXX.";
                            leaf profile-id {
                                type leafref {
                                    path "/l2vpn-ntw/vpn-services/vpn-service"  + "/global-parameters-profiles"  + "/global-parameters-profile/profile-id";
                                }
                                description
                                    "XXXX.";
                            }
                        }
                    }
                    uses vpn-common:service-status;
                    container vpn-network-accesses {
                        description
                            "List of VPN Nodes.";
                        list vpn-network-access {
                            key "id";
                            description
                                "List of VPN Network Accesses.";
                            leaf id {
                                type vpn-common:vpn-id;
                                description
                                    "Identifier of network access";
                            }
                            leaf description {
                                type string;
                                description
                                    "String to describe the element.";
                            }
                            leaf port-id {
                                type vpn-common:vpn-id;
                                description
                                    "NE Port-id";
                            }

                            uses vpn-common:service-status;
                            container connection {
                                description
                                    "Container for bearer";
                                container encapsulation {
                                    description
                                        "Container for dot1Q Interface";
                                    leaf l2-access-type {
                                        type identityref {
                                            base vpn-common:encapsulation-type;
                                        }
                                        description
                                            "L2 Access encapsulation type.";
                                    }
                                    container dot1q {
                                        when "../l2-access-type='vpn-common:dot1q'";
                                        if-feature "vpn-common:dot1q";
                                        description
                                            "Qot1q";
                                        leaf c-vlan-id {
                                            type uint32;
                                            description
                                                "VLAN identifier";
                                        }
                                    }
                                    container qinq {
                                        when "../l2-access-type='vpn-common:qinq'";
                                        if-feature "vpn-common:qinq";
                                        description
                                            "QinQ";
                                        leaf s-vlan-id {
                                            type uint32;
                                            description
                                                "S-VLAN Identifier";
                                        }
                                        leaf c-vlan-id {
                                            type uint32;
                                            description
                                                "C-VLAN Identifier";
                                        }
                   
                                        leaf  c-vlan-id-range{
                                            type string;
                                            description 
                                                "Multiple C-VLAN id.";
                                        }
  	                                    leaf  s-vlan-id-range{
                                            type string;
                                            description 
                                                "Multiple S-VLAN id.";
                                        }
                                    }//end of qinq
                                }//end of encapsulation
                  /*
                   * add vlan-action  and action-vlan-id, --create by xwu
                   */  
                                leaf vlan-action {
                                    description
                                        "vlan-action. ";
                                    reference
                                        "";
                                    type enumeration {
                                        enum Keep {
                                            description
                                                "keep  vlan id";
                                        }
                                        enum  Push {
                                            description
                                                "add  vlan id ";
                                        }
                                        enum  Pop{
                                            description
                                                "delete vlan id.";
                                        }     
                                        enum  Swap{
                                            description
                                                "modify vlan id.";
                                        }       
                                    } //end of enumeration
                                } //end of vlan-action
                                leaf action-vlan-id {
                                    type uint32;
                                    description
                                        "This parameter needs to be configured only when 'vlan-action' value is Push and Swap ";
                                }
                            }//end of connection
                //}

               // }
                            container service {
                                description
                                    "Container for service";
                                leaf mtu {
                                    type uint32;
                                    description
                                        "MTU, it is also known as the maximum
                                        transmission unit or maximum frame size. When a
                                        frame is larger than the MTU, it is broken down,
                                        or fragmented, into smaller pieces by the
                                        network protocol to accommodate the MTU of the network";
                                }
                                container svc-input-bandwidth {
                                    if-feature "vpn-common:input-bw";
                                    description
                                        "From the PE perspective, the service input bandwidth of the connection.";
                                    list input-bandwidth {
                                        key "type";
                                        description
                                            "List for input bandwidth";
                                        leaf type {
                                            type identityref {
                                                base vpn-common:bw-type;
                                            }
                                            description
                                                "Bandwidth Type";
                                        }
                                        leaf cir {
                                            type uint64;
                                            description
                                                "Committed Information Rate. The maximum number of
                                                bits that a port can receive or send during
                                                one-second over an interface.";
                                        }
                                        leaf cbs {
                                            type uint64;
                                            description
                                                "Committed Burst Size.CBS controls the bursty nature
                                                    of the traffic. Traffic that does not use the
                                                configured CIR accumulates credits until the credits
                                                reach the configured CBS.";
                                        }
                                        leaf eir {
                                            type uint64;
                                            description
                                                "Excess Information Rate,i.e.,Excess frame delivery allowed not subject to SLA.The traffic rate can be limited by eir.";
                                        }
                                        leaf ebs {
                                            type uint64;
                                            description
                                                "Excess Burst Size. The bandwidth available for burst
                                                traffic from the EBS is subject to the amount of
                                                bandwidth that is accumulated during periods when
                                                traffic allocated by the EIR policy is not used.";
                                        }
                                        leaf pir {
                                            type uint64;
                                            description
                                                "Peak Information Rate, i.e., maixmum frame delivery allowed. It is equal to or less than sum of cir and eir.";
                                        }
                                        leaf pbs {
                                            type uint64;
                                            description
                                                "Peak Burst Size. It is measured in bytes per second.";
                                        }
                                    }
                                }//end of svc-input-bandwidth
                                container svc-output-bandwidth {
                                    if-feature "output-bw";
                                    description
                                        "From the PE perspective, the service output bandwidth of the connection.";
                                    list output-bandwidth {
                                        key "type";
                                        description
                                            "List for output bandwidth";
                                        leaf type {
                                            type identityref {
                                                base vpn-common:bw-type;
                                            }
                                            description
                                                "Bandwidth Type";
                                        }
                                        leaf cos-id {
                                            type uint8;
                                            description
                                                "Identifier of Class of Service, indicated by DSCP or a CE-CLAN CoS(802.1p)value in the service frame.";
                                        }
                                        leaf cir {
                                            type uint64;
                                            description
                                                "Committed Information Rate. The maximum number of bits that a port can receive or send during one-second over an interface.";
                                        }
                                        leaf cbs {
                                            type uint64;
                                            description
                                                "Committed Burst Size.CBS controls the bursty nature of the traffic. Traffic that does not use the
                                                configured CIR accumulates credits until the credits reach the configured CBS.";
                                        }
                                        leaf eir {
                                            type uint64;
                                            description
                                                "Excess Information Rate,i.e.,Excess frame delivery allowed not subject to SLA.The traffic rate can be limited by eir.";
                                        }
                                        leaf ebs {
                                            type uint64;
                                            description
                                                "Excess Burst Size. The bandwidth available for burst
                                                traffic from the EBS is subject to the amount of
                                                bandwidth that is accumulated during periods when
                                                traffic allocated by the EIR policy is not used.";
                                        }
                                        leaf pir {
                                            type uint64;
                                            description
                                                "Peak Information Rate, i.e., maixmum frame delivery
                                                allowed. It is equal to or less than sum of cir and
                                                eir.";
                                        }
                                        leaf pbs {
                                            type uint64;
                                            description
                                                "Peak Burst Size. It is measured in bytes per second.";
                                        }
                                    }
                                }//end of svc-output-bandwidth
                  container qos {
                    if-feature "vpn-common:qos";
                    description
                      "QoS configuration.";
                    container qos-classification-policy {
                      description
                        "Configuration of the traffic classification
                         policy.";
                      list rule {
                        key "id";
                        ordered-by user;
                        description
                          "List of classification rules.";
                        leaf id {
                          type string;
                          description
                            "A description identifying the QoS classification
                             policy rule.";
                        }
                        choice match-type {
                          default "match-flow";
                          description
                            "Choice for classification.";
                          case match-flow {
                            container match-flow {
                              description
                                "Describes flow-matching criteria.";
                              leaf dscp {
                                type inet:dscp;
                                description
                                  "DSCP value.";
                              }
                              leaf dot1q {
                                type uint16;
                                description
                                  "802.1Q matching.  It is a VLAN tag added into
                                   a frame.";
                              }
                              leaf pcp {
                                type uint8 {
                                  range "0..7";
                                }
                                description
                                  "PCP value.";
                              }
                              leaf src-mac {
                                type yang:mac-address;
                                description
                                  "Source MAC address.";
                              }
                              leaf dst-mac {
                                type yang:mac-address;
                                description
                                  "Destination MAC address.";
                              }
                              leaf color-type {
                                type identityref {
                                  base color-type;
                                }
                                description
                                  "Color types.";
                              }
                              leaf any {
                                type empty;
                                description
                                  "Allow all.";
                              }
                            }
                          }
                          case match-application {
                            leaf match-application {
                              type identityref {
                                base vpn-common:customer-application;
                              }
                              description
                                "Defines the application to match.";
                            }
                          }
                        }
                        leaf target-class-id {
                          type string;
                          description
                            "Identification of the CoS.
                             This identifier is internal to the
                             administration.";
                        }
                      }
                    }
                    container qos-profile {
                      description
                        "QoS profile configuration.";
                      list qos-profile {
                        key "profile";
                        description
                          "QoS profile.
                           Can be standard profile or customized
                           profile.";
                        leaf profile {
                          type leafref {
                            path "/l2vpn-ntw/vpn-profiles"
                               + "/valid-provider-identifiers"
                               + "/qos-profile-identifier/id";
                          }
                          description
                            "QoS profile to be used.";
                        }
                        leaf direction {
                          type identityref {
                            base vpn-common:qos-profile-direction;
                          }
                          default "vpn-common:both";
                          description
                            "The direction to which the QoS profile
                             is applied.";
                        }
                      }
                    }
                  }//end of qos
                  container mac-policies {
                    description
                      "Container for MAC-related policies.";
                    container access-control-list {
                      description
                        "Container for access control List.";
                      list mac {
                        key "mac-address";
                        description
                          "List for MAC addresses.";
                        leaf mac-address {
                          type yang:mac-address;
                          description
                            "Specifies a MAC address.";
                        }
                      }
                    }
                    container mac-loop-prevention {
                      description
                        "Container of MAC loop prevention.";
                      leaf frequency {
                        type uint32;
                        description
                          "Frequency";
                      }
                      leaf protection-type {
                        type identityref {
                          base loop-prevention-type;
                        }
                        description
                          "Protection type";
                      }
                      leaf number-retries {
                        type uint32;
                        description
                          "Number of retries";
                      }
                    }
                    container mac-addr-limit {
                      description
                        "Container of MAC-Addr limit configurations";
                      leaf mac-num-limit {
                        type uint16;
                        description
                          "maximum number of MAC addresses learned from
                           the subscriber for a single service instance.";
                      }
                      leaf time-interval {
                        type uint32;
                        units "milliseconds";
                        description
                          "The aging time of the mac address.";
                      }
                      leaf action {
                        type identityref {
                          base mac-action;
                        }
                        description
                          "specify the action when the upper limit is
                           exceeded: drop the packet, flood the
                           packet, or simply send a warning log message.";
                      }
                    }
                  }//end of mac-policies
                  container broadcast-unknown-unicast-multicast {
                    description
                      "Container of broadcast, unknown unicast, and multicast
                       configurations";
                    leaf multicast-site-type {
                      type enumeration {
                        enum receiver-only {
                          description
                            "The site only has receivers.";
                        }
                        enum source-only {
                          description
                            "The site only has sources.";
                        }
                        enum source-receiver {
                          description
                            "The site has both sources and receivers.";
                        }
                      }
                      default "source-receiver";
                      description
                        "Type of multicast site.";
                    }
                    list multicast-gp-address-mapping {
                      key "id";
                      description
                        "List of Port to group mappings.";
                      leaf id {
                        type uint16;
                        description
                          "Unique identifier for the mapping.";
                      }
                      leaf vlan-id {
                        type uint32;
                        description
                          "The VLAN ID of the Multicast group.";
                      }
                      leaf mac-gp-address {
                        type yang:mac-address;
                        description
                          "The MAC address of the Multicast group.";
                      }
                      leaf port-lag-number {
                        type uint32;
                        description
                          "The ports/LAGs belonging to the Multicast group.";
                      }
                    }
                    leaf bum-overall-rate {
                      type uint32;
                      description
                        "overall rate for BUM";
                    }
                  }//END of  container broadcast-unknown-unicast-multicast
                }//end of container service
              }// end of list vpn-network-access
            }// end of container vpn-network-accesses
          }// end of container vpn-nodes
         }//container vpn-nodes   
          
  	 /*
			* add container pw-trails, --create by xwu
			*/
    
    container pw-trails{
    	 description
        "Container for pw-trails";
      list pw-trail {
        key "id";
        description
          "list of pw-trail";
			    
			     leaf id {
			          type vpn-common:vpn-id;
			          description
			            "pw-trail id";
			        }
			    
			     leaf pw-protection {
			          description
			            "pw protection type";
			            
			       type	enumeration {
				        enum pw-1:1 {
				          description
				            "pw 1:1 protection type.";
				        }
				       enum  pw-redundancy{
				          description
				            "pw redundancy protection type.";
				        }
			        }// end of enumeration
  
        }
    
      container pws {
            description
        	"Container for pws";
        	
            list pw {
       				 key "id";
        			description
         			 "list of pw";
    
 			     leaf id {
			          type string;
			          description
			            "pw id";
			        }   
    
    
       leaf pw-role {
			          description
			            "pw role";
			            
			       type	enumeration {
				        enum  master{
				          description
				            "master pw.";
				        }
				       enum  slave{
				          description
				            "slave pw.";
				        }
				     enum  DNI-PW{
				          description
				            "DNI PW.";
				        } 
			        }// end of enumeration
  
        }
    
         leaf  signaling-type{
			          description
			            "PW signaling type";
			            
			       type	enumeration {
				        enum  static-pw{
				          description
				            "static pw.";
				        }
				       enum  dynamic-pw{
				          description
				            "dynamic pw.";
				        }
				   
			        }// end of enumeration
  
        }
   
         leaf  encaplate-type{
         			   type identityref {
                        base vpn-common:encapsulation-type;
                      }
			          description
			            "PW encaplate type";
			       }
    

          leaf  vcid{
         			  type	string;
			          description
			            "PW vc id";
			       }
 /*
   * add 'control-word-negotiation' attribute, --create by xwu
   */      
        leaf control-word-negotiation {
      type boolean;
      description
        "Controls whether Control-word negotiation is enabled
         (if set to true) or not (if set to false).";
      reference
        "Section 7 of RFC8077";
    }  
                   

  /*
   * add cv-type attribute, --create by xwu
   */
    
   leaf cv-type {
     description
        "BFD CV Types for PW. ";
      reference
        "Section 3.3 of RFC5885";
   
        type    enumeration {
        enum bfd-ipudp-fd {
          description
            "BFD IP/UDP-encapsulated, for PW Fault Detection only.";
        }
        
            enum  bfd-ipudp-fs+bfd-ipudp-fd {
          description
            "BFD IP/UDP-encapsulated, for PW Fault Detection and
                    AC/PW Fault Status Signaling.";
        }
        
            enum  bfd-pwach-fd{
          description
            "BFD PW-ACH-encapsulated, for PW Fault Detection only.";
        }     
       
         enum  bfd-pwach-fs+bfd-pwach-fd{
          description
            "BFD PW-ACH-encapsulated, for PW Fault Detection and
                    AC/PW Fault Status Signaling.";
        }       
        
        } //end of enumeration
     
    } //end of cv-type 

          leaf  ingress-ne-id{
         			  type	string;
			          description
			            "PW ingress ne id";
			       }
			       
          leaf  egress-ne-id{
         			  type	string;
			          description
			            "PW egress ne id";
			       }

					//tunnels
					//uses te:tunnels-grouping;
					
		container pw-bandwidth {
            description "pw-qos";
            list pw-bandwidth-grouping {
                key "type";
                      description
                        "List for input bandwidth";
                      leaf type {
                        type identityref {
                          base vpn-common:bw-type;
                        }
                        description
                          "Bandwidth Type";
                      }
                      leaf cos-id {
                        type uint8;
                        description
                          "Identifier of Class of Service
                           , indicated by DSCP or a CE-CLAN
                           CoS(802.1p)value in the service frame.";
                      }
                      leaf cir {
                        type uint64;
                        description
                          "Committed Information Rate. The maximum number of
                           bits that a port can receive or send during
                           one-second over an interface.";
                      }
                      leaf cbs {
                        type uint64;
                        description
                          "Committed Burst Size.CBS controls the bursty nature
                           of the traffic. Traffic that does not use the
                           configured CIR accumulates credits until the credits
                           reach the configured CBS.";
                      }
                      leaf eir {
                        type uint64;
                        description
                          "Excess Information Rate,i.e.,Excess frame delivery
                           allowed not subject to SLA.The traffic rate can be
                           limited by eir.";
                      }
                      leaf ebs {
                        type uint64;
                        description
                          "Excess Burst Size. The bandwidth available for burst
                           traffic from the EBS is subject to the amount of
                           bandwidth that is accumulated during periods when
                           traffic allocated by the EIR policy is not used.";
                      }
                      leaf pir {
                        type uint64;
                        description
                          "Peak Information Rate, i.e., maixmum frame delivery
                           allowed. It is equal to or less than sum of cir and
                           eir.";
                      }
                      leaf pbs {
                        type uint64;
                        description
                          "Peak Burst Size. It is measured in bytes per second.";
                      }
            }
		}
		
		container tunnels {
            description
        	"Container for tunnels";
        	
            list tunnel {
       				 key "name";
        			description
         			 "list of tunnel";
    
 			     leaf name {
			          type string;
			          description
			            "tunnel name";
			        }   
			        
			        }//end  list of tunnel
			        
			        }// end container of tunnels
					
					

        leaf  ingress-incoming-label{
         			  type	rt-types:mpls-label;
			          description
			            "PW ingress incoming label";
			       }          leaf  ingress-outgoing-label{
         			  type	rt-types:mpls-label;
			          description
			            "PW ingress outgoing label";
			       }
			       
          leaf  egress-incoming-label{
         			  type	rt-types:mpls-label;
			          description
			            "PW egress-incoming-label";
			       }			       

          leaf  egress-outgoing-label{
         			  type	rt-types:mpls-label;
			          description
			            "PW egress-outgoing-label";
			       }
    
   		 		}//end of pw list
    
    		}
 
    }// end of pw-trail list
    
    }
       
       container service-bfd-policy{
       		uses te-mpls:bfd-policy;
					}
        }// end of list vpn-service
      }// end of container vpn-services
  }// end of l2vpn-ntw
  

	 /*
	* add rpc for split horizon group, --create by xwu
	*/

  rpc create-split-horizon-group {
	  input {	
	  	container horizontal-split-groups{
	  			list horizontal-split-group{
	  			  key "group-id";
	  		    description
             "List for horizontal-split-group.";
	  			
	  	    leaf group-id {
		          type string;
		  		        }
			  			
	  	    leaf ne-id {
		          type string;
		  		        }	  			
	  			
	  		 leaf vpn-id {
					 type vpn-common:vpn-id;
			    }   	  			
	  			
	  			container members{
	  				list member{
			  			 key "member-id";
			  		    description
		             "List for horizontal-split-group members.";
			  				
	  				 	leaf member-id {
		         	 type string;
		  		        }	  		
	  				
	  					leaf member-type {
			         	type enumeration {
										enum tp {
											 description
				            		"UNI tp member.";
										}
										enum pw {
											 description
				                "pw member.";
										}
									}
		  		    }	 
	  				}// end of list member
	  			 }// end of container members	
	  			}//end of list
	  	}//end of container horizontal-split-groups

	  }// end of input 
  
  }//end of rpc
  
  
  
    rpc delete-split-horizon-group {
  input {
	  	container horizontal-split-groups{
	  			list horizontal-split-group{
	  			  key "group-id";
	  		    description
             "List for horizontal-split-group.";
	  			
	  	    leaf group-id {
		          type string;
		  		        }
			  			
	  	    leaf ne-id {
		          type string;
		  		        }	  
		  		        
	  		 leaf vpn-id {
					 type vpn-common:vpn-id;
			    }          			
	  			
	  			}//end of list
	  	}//end of container horizontal-split-groups

	  }// end of input 
  
  }//end of rpc
  
   
  
    rpc query-split-horizon-group {
     input {
		   		 leaf vpn-id {
				      type vpn-common:vpn-id;
				      description
				        "VPN identifier.
				         This identifier has a local meaning.";
				    }  
		    }
		    
		  output {
					  leaf vpn-id {
				      type vpn-common:vpn-id;
				      description
				        "VPN identifier.
				         This identifier has a local meaning.";
				    }
			  	
			  	container horizontal-split-groups{
			  			list horizontal-split-group{
			  			  key "group-id";
			  		    description
		             "List for horizontal-split-group.";
			  			
			  	    leaf group-id {
				          type string;
				  		        }
					  			
			  	    leaf ne-id {
				          type string;
				  		        }	  		
				  		        
				  		 leaf vpn-id {
				     		 type vpn-common:vpn-id;
				     					    }          
				  		        	
			  			
			  			container members{
			  				list member{
					  			 key "member-id";
					  		    description
				             "List for horizontal-split-group members.";
					  				
			  				 	leaf member-id {
				         	 type string;
				  		        }	  		
			  				
			  					leaf member-type {
					         	type enumeration {
												enum tp {
													 description
						            		"UNI tp member.";
												}
												enum pw {
													 description
						                "pw member.";
												}
											}
				  		    }	 
			  				}// end of list member
			  			 }// end of container members	
			  			}//end of list
			  	}//end of container horizontal-split-groups

			  }// end of output 
  
  }//end of rpc
  
  
  
  
  
  
}// end of module
